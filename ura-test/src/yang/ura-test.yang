module ura-test {
  namespace "http://spritelink.net/ns/uratest";
  prefix ura-test;

  import ietf-inet-types {
    prefix inet;
  }
  import tailf-common {
    prefix tailf;
  }
  import tailf-ncs {
    prefix ncs;
  }

  augment /ncs:services {

    list ura-test {
      description "This is an RFS skeleton service";

      key name;
      leaf name {
        tailf:info "Unique service id";
        tailf:cli-allow-range;
        type string;
      }

      uses ncs:service-data;
      ncs:servicepoint ura-test-servicepoint;

      // replace with your own stuff here
      leaf integer-range {
        type string;
      }
      leaf num-requests {
        type uint8;
        default 1;
      }
    }
  }
}
