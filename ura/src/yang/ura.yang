module ura {
  namespace "http://spritelink.net/ns/ura";
  prefix ura;

  import ietf-inet-types {
    prefix inet;
  }
  import tailf-common {
    prefix tailf;
  }
  import tailf-ncs {
    prefix ncs;
  }

  augment /ncs:services {

    container ura {
      description "Universal Resource Allocator";

      list integer {
        description "Define pool/range for integer (uint64) allocations";

        key name;
        leaf name {
          tailf:info "Unique id of integer range";
          tailf:cli-allow-range;
          type string;
        }

        uses ncs:service-data;
        ncs:servicepoint ura-servicepoint;

        leaf description {
          description "Description of range";
          type string;
        }

        leaf min-value {
          description "Minimum value";
          type uint64;
          default 0;
        }

        leaf max-value {
          description "Maximum value";
          type uint64;
          default 4294967296;
          //default 18446744073709551615; // Java can't handle this big numbers right now
        }

        leaf allocation-order {
          description "Specify order of allocation";
          default "ascending";
          type enumeration {
            enum "ascending" {
              value 0;
              description "Allocate integers in ascending order";
            }
            enum "descending" {
              value 1;
              description "Allocate integers in descending order";
            }
          }
        }

        leaf allocation-method {
          description "Control the method used to find the next free integer";

          default "max";
          type enumeration {
            enum "max" {
              value 0;
              description "Allocate current maximum value + 1";
            }
            enum "first" {
              value 1;
              description "Allocate first available number";
            }
          }
        }

        list request {
          key name;

          leaf name {
            tailf:info "Unique id of request for integer";
            tailf:cli-allow-range;
            type string;
          }

          unique integer;

          leaf integer {
            type uint64;
            config false;
            tailf:cdb-oper {
              tailf:persistent true;
            }
          }

          leaf redeploy-service {
            description "Redeploy service after succesful allocation";
            type string;
//            type leafref {
//              path "/ncs:services/name";
//            }
          }
        }

      }
    }
  }
}
